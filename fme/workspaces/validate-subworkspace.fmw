FME workspace validate-subworkspace.fmw

Parameters:
- SourceDataset_ACAD = C:\safegit\fmepedia-validation\www\download\distribution_N25_bad.dwg   # Source Autodesk AutoCAD DWG/DXF File(s)

Readers:
- ACAD_1: ACAD from $(SourceDataset_ACAD) in EPSG:2277

Writers:
- TEXTLINE_1: TEXTLINE to file.html
- ACAD_2: ACAD to errors.dwg

water_distribution_lines (reader ACAD_1)
    attributes: ANNO_DIAM char(4), COMPKEY number(2,0), COMPTYPE number(2,0), DIAMETER number(3,0), DRAW number(2,0), FEATURE_ID char(25), LEAD_MAIN_ number(3,0), MATERIAL char(8), PROJECT char(9), PR_ZONE char(4), STATUS char(3), SYMCODE number(4,0), SYMCODE2 number(4,0), TILE char(4), WNM_TYPE char(8), YEAR_INSTA number(5,0)
    -> GeometryFilter
GeometryFilter
    GEOM_PORT_NAMES = Line
    BREAK_AGG = No
    LINE -> GeometryValidator
    LINE -> FeatureHolder
Sampler
    RATE = 1
    SAMPLE_TYPE_LONG = First N Features
    SAMPLED -> UUIDGenerator
UUIDGenerator
    UUID_ATTR = _uuid
    -> VariableSetter_3
VariableSetter_3
    VALUE = @Value(_uuid)
    SCOPE = Global
    VARNAME = uuid
VariableRetriever_4
    SCOPE = Global
    VALUE_ATTR = _uuid
    VARNAME = uuid
    -> error_features (writer ACAD_2)
    -> Labeller
error_features (writer ACAD_2)
    attributes: ANNO_DIAM char(4), COMPKEY number(2,0), COMPTYPE number(2,0), DIAMETER number(3,0), DRAW number(2,0), FEATURE_ID char(25), LEAD_MAIN_ number(3,0), MATERIAL char(8), PROJECT char(9), PR_ZONE char(4), STATUS char(3), SYMCODE number(4,0), SYMCODE2 number(4,0), TILE char(4), WNM_TYPE char(8), YEAR_INSTA number(5,0)
Labeller
    DIST = 1
    LABATTR = @Value(error_label)
    OVERLAPS = Yes
    AVERAGE_CHAR_WIDTH = 1
    PARROTATTR = _parallel_rotation
    SPACE = 0
    MIN = 0
    SPOT_CHOICE = Above or Right
    ENDS = yes
    TANROTATTR = _label_rotation
    HEIGHT = 1
    LABEL -> error_types (writer ACAD_2)
error_types (writer ACAD_2)
FeatureHolder
    -> VariableRetriever_3
VariableRetriever_3
    SCOPE = Global
    VALUE_ATTR = _invalidFeatures
    VARNAME = _invalidFeatures
    -> Tester_2
Tester_2
    TEST_DESCRIPTION = ""
    BOOL_OP = OR
    TEST_MODE = Automatic
    TEST_CLAUSE = TEST @Value(_invalidFeatures) NOT_= yes
    PASSED -> Aggregator
text_line (writer TEXTLINE_1)
    attributes: text_line_data buffer

Bookmark: Validation
GeometryValidator
    ISSUE_ATTR_NAME = _issues
    OGC_SIMPLE_CHECK = OGC_SIMPLE_CHECK
    PRESETS = OGC
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    OGC_VALID_CHECK = OGC_VALID_CHECK
    REPAIR = No
    FAILED -> VariableSetter
    PASSED -> Tester
VariableSetter
    VALUE = yes
    SCOPE = Global
    VARNAME = _invalidFeatures
    -> AttributeCreator_2
AttributeCreator_2
    ATTR_LIST = error_label,Geometry
    -> DWGStyler
DWGStyler
    COLOR = 0.619608,0.0823529,1
    DWGStyled -> Cloner
Tester
    TEST_DESCRIPTION = ""
    BOOL_OP = OR
    TEST_MODE = Automatic
    TEST_CLAUSE = TEST @Value(DIAMETER) NOT_= 0
    FAILED -> VariableSetter_2
VariableSetter_2
    VALUE = yes
    SCOPE = Global
    VARNAME = _invalidFeatures
    -> AttributeCreator_3
AttributeCreator_3
    ATTR_LIST = error_label,Attribute: DIAMETER
    -> DWGStyler_2
DWGStyler_2
    COLOR = 0.596078,1,0.698039
    DWGStyled -> Cloner
Cloner
    COPIES = 1
    COPYATT = _copynum
    COPY -> XMLTemplater_2
    COPY -> Sampler
    COPY -> VariableRetriever_4
XMLTemplater_2
    RESULT_ATTRIBUTE = Remarks
    OUTPUT_XML_HEADER = No
    ROOT_QUERY_EXPR:
      <div style="min-width: 200px;">Invalid {fme:get-attribute("error_label")}
      </div>
    VISIBLE_QUERY_VALIDATE = No
    -> AttributeCreator

Bookmark: Report creation
AttributeCreator
    ATTR_LIST = _invalid_features,yes
    -> GoogleStaticMapCreator
GoogleStaticMapCreator
    -> XMLTemplater_3 [input 2]
Creator
    GEOMTYPE = Geometry Object
    NUM = 1
    CREATED -> VariableRetriever_2
VariableRetriever_2
    SCOPE = Global
    VALUE_ATTR = _invalidFeatures
    VARNAME = _invalidFeatures
    -> VariableRetriever
VariableRetriever
    SCOPE = Global
    VALUE_ATTR = _uuid
    VARNAME = uuid
    -> Tester_3
Tester_3
    TEST_DESCRIPTION = ""
    BOOL_OP = OR
    TEST_MODE = Automatic
    TEST_CLAUSE = TEST @Value(_invalidFeatures) = yes
    PASSED -> XMLTemplater_3 [input 1]
XMLTemplater_3
    RESULT_ATTRIBUTE = _htmlTable
    ROW_QUERY_EXPR:
      <tr>
      <td>{fme:get-attribute("TILE")}</td>
      <td>{fme:get-attribute("FEATURE_ID")}</td>
      <td>{fme:get-attribute("DIAMETER")}</td>
      <td>{fme:get-attribute("WNM_TYPE")}</td>
      <td>{fme:get-xml-attribute("Remarks")}</td>
      <td><img src='{fme:get-attribute("_StaticMapUrl")}'></img></td>
      </tr>
    OUTPUT_XML_HEADER = No
    ROOT_QUERY_EXPR:
      <table>
      <tr>
      <th>TILE</th>
      <th>FEATURE_ID</th>
      <th>DIAMETER</th>
      <th>WNM_TYPE</th>
      <th>Error Remarks</th>
      <th>Map</th>
      </tr>
      {fme:process-features("ROW")}
      </table>
    VISIBLE_QUERY_VALIDATE = No
    -> StringConcatenator
StringConcatenator
    ACTION = Create New Attribute
    PARM_LINE:
      <!DOCTYPE html>
      <html>
      <head>
        <meta charset="utf-8">

        <!-- Use the .htaccess and remove these lines to avoid edge case issues. More info: h5bp.com/i/378 -->
        <meta http-equiv="X-UA-Compatible" content="IE=edge,chrome=1">

        <title>Data validation failure</title>
        <meta name="description" content="">

        <!-- Mobile viewport optimized: h5bp.com/viewport -->
        <meta name="viewport" content="width=device-width">

        <!-- CSS goes in the document HEAD or added to your external stylesheet -->
          <style type="text/css">
          /* ------------------
           styling for the tables
             ------------------   */
          body {
              font-family: 'Lucida Sans Unicode', 'Lucida Grande', Sans-Serif;
          }
          table {
            line-height: 1.6em;
            font-size: 12px;
            background: #fff;
            border-collapse: collapse;
            text-align: left;
          }

          th {
            font-size: 14px;
            font-weight: normal;
            color: #039;
            padding: 10px 8px;
            border-bottom: 2px solid #6678b1;
          }

          tr {
            color: #669;
            padding: 9px 8px 0px 8px;
          }

          </style>

      </head>
      <body>

      <h1>Validation FAILED</h1>
      <p><a href="$(FME_SERVER_WEB_URL)/fmerest/v2/resources/FME_SHAREDRESOURCE_TEMP/filesys/CADError/errors_@Value(_uuid).dwg?token=66da6d2b1f4b4681451a8f9043ad653a756fdb03&accept=contents">Download failed features</a></p>

      @Value(_htmlTable)

      </body>
      </html>
    VAL_ATTR = text_line_data
    -> text_line (writer TEXTLINE_1)

Bookmark: HTML report for success
Aggregator
    SEP = ,
    ACCUM_ATTRS_NAME = No
    MODE = Attributes Only
    COUNT_ATTR = _count
    ORDERED = No
    AGGREGATE -> TimeStamper
Note: Timestamp according to locale
TimeStamper
    TIME_ATTR = _timestamp
    FMT = ^c
    -> StringConcatenator_2
StringConcatenator_2
    ACTION = Create New Attribute
    PARM_LINE:
      <!doctype html>
      <head>
        <meta charset="utf-8">

        <!-- Use the .htaccess and remove these lines to avoid edge case issues. More info: h5bp.com/i/378 -->
        <meta http-equiv="X-UA-Compatible" content="IE=edge,chrome=1">

        <title></title>
        <meta name="description" content="">

        <!-- Mobile viewport optimized: h5bp.com/viewport -->
        <meta name="viewport" content="width=device-width">


      </head>
      <body>
      <h1>Validation SUCCEEDED</h1>
          <p>Load Complete - Data Validation was Successful</p>
          <p>Date Loaded:  @Value(_timestamp)<br>
          Number of Features Added: @Value(_count)</p>
      </body>
      </html>
    VAL_ATTR = text_line_data
    -> text_line (writer TEXTLINE_1)

FME custom transformer GoogleStaticMapCreator

Input (input)
    -> Reprojector
Reprojector
    SOURCE = TX83-CF
    STROKE_ARCS = Yes
    RASTER_CELL_SIZE = Preserve Cells
    INTERPOLATION_TYPE_NAME = Nearest Neighbor
    DEST = EPSG:4326
    REPROJECTED -> CoordinateSwapper
CoordinateSwapper
    SWAP_TYPE = X <-> Y
    -> GeometryExtractor
GeometryExtractor
    ATTR = _geometry
    OGCVERSION = 1.1
    KIND_LONG = OGC Well Known Text
    -> SubstringExtractor
SubstringExtractor
    SRC_ATTR = _geometry
    START = 12
    END = -2
    RESULT_ATTR = _path
    -> StringReplacer_2
StringReplacer_2
    NO_MATCH = _FME_NO_OP_
    REGEXP = no
    FIND_TEXT = ,
    REPLACE_TEXT = |
    CASE = no
    SRC_ATTRS = _path
    -> StringReplacer
StringReplacer
    NO_MATCH = _FME_NO_OP_
    REGEXP = no
    FIND_TEXT = " "
    REPLACE_TEXT = ,
    CASE = no
    SRC_ATTRS = _path
    -> CoordinateExtractor
CoordinateExtractor
    Y_ATTR = _y
    X_ATTR = _x
    Z_DEFAULT = -9999
    IND = 0
    Z_ATTR = _z
    -> StringConcatenator_5
StringConcatenator_5
    PARM_LINE = http://maps.googleapis.com/maps/api/staticmap?center=@Value(_x),@Value(_y)&amp&amp&size=200x200&amp&sensor=false&path=color:0x0000ff|weight:5|@Value(_path)&key=AIzaSyAAJ9HjDtsSOYUzLI6Xkvfc8RMHOi6RfIs
    VAL_ATTR = _StaticMapUrl
    -> Output (output)
Output (output)
