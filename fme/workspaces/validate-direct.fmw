FME workspace validate-direct.fmw

Parameters:
- SourceDataset_ACAD =   # Source Autodesk AutoCAD DWG/DXF File(s)

Readers:
- ACAD_1: ACAD from $(SourceDataset_ACAD) in EPSG:2277

Writers:
- TEXTLINE_1: TEXTLINE to file.html
- ACAD_2: ACAD to $(FME_SHAREDRESOURCE_TEMP)/CADError

water_distribution_lines (reader ACAD_1)
    attributes: ANNO_DIAM char(4), COMPKEY number(2,0), COMPTYPE number(2,0), DIAMETER number(3,0), DRAW number(2,0), FEATURE_ID char(25), LEAD_MAIN_ number(3,0), MATERIAL char(8), PROJECT char(9), PR_ZONE char(4), STATUS char(3), SYMCODE number(4,0), SYMCODE2 number(4,0), TILE char(4), WNM_TYPE char(8), YEAR_INSTA number(5,0)
    -> GeometryFilter
GeometryFilter
    BREAK_AGG = No
    GEOM_PORT_NAMES = Line
    LINE -> Counter_2
    LINE -> FeatureHolder
Sampler
    RATE = 1
    SAMPLE_TYPE_LONG = First N Features
    SAMPLED -> UUIDGenerator
UUIDGenerator
    UUID_ATTR = _uuid
    -> VariableSetter_3
VariableSetter_3
    SCOPE = Global
    VALUE = @Value(_uuid)
    VARNAME = uuid
VariableRetriever_4
    SCOPE = Global
    VALUE_ATTR = _uuid
    VARNAME = uuid
    -> error_features (writer ACAD_2)
    -> Labeller
error_features (writer ACAD_2)
    attributes: ANNO_DIAM char(4), COMPKEY number(2,0), COMPTYPE number(2,0), DIAMETER number(3,0), DRAW number(2,0), FEATURE_ID char(25), LEAD_MAIN_ number(3,0), MATERIAL char(8), PROJECT char(9), PR_ZONE char(4), STATUS char(3), SYMCODE number(4,0), SYMCODE2 number(4,0), TILE char(4), WNM_TYPE char(8), YEAR_INSTA number(5,0)
Labeller
    AVERAGE_CHAR_WIDTH = 1
    DIST = 1
    ENDS = yes
    HEIGHT = 1
    LABATTR = @Value(error_label)
    MIN = 0
    OVERLAPS = Yes
    PARROTATTR = _parallel_rotation
    SPACE = 0
    SPOT_CHOICE = Above or Right
    TANROTATTR = _label_rotation
    LABEL -> error_types (writer ACAD_2)
error_types (writer ACAD_2)
FeatureHolder
    -> VariableRetriever_3
VariableRetriever_3
    SCOPE = Global
    VALUE_ATTR = _invalidFeatures
    VARNAME = _invalidFeatures
    -> Tester_2
Tester_2
    BOOL_OP = OR
    TEST_CLAUSE = TEST @Value(_invalidFeatures) NOT_= yes
    TEST_MODE = Automatic
    PASSED -> Aggregator
text_line (writer TEXTLINE_1)
    attributes: text_line_data buffer

Bookmark: Validation
Counter_2
    CNT_ATTR = _totalCount
    DOMAIN = totalcount
    SCOPE = Global
    START = 1
    -> Sampler_2
Sampler_2
    RATE = 1
    SAMPLE_MODE = No
    SAMPLE_TYPE_LONG = Last N Features
    SAMPLED -> VariableSetter_4
    NOT_SAMPLED -> GeometryValidator
VariableSetter_4
    SCOPE = Global
    VALUE = @Value(_totalCount)
    VARNAME = totalChecked
    -> GeometryValidator
GeometryValidator
    ISSUE_ATTR_NAME = _issues
    OGC_SIMPLE_CHECK = OGC_SIMPLE_CHECK
    OGC_VALID_CHECK = OGC_VALID_CHECK
    PRESETS = OGC
    REPAIR = No
    RULES = NAN_REMOVAL%""%"Yes"%NULL_REMOVAL%""%"Yes"%CONSECUTIVE_IDENTICAL_VERTICES_2D%CONSECUTIVE_IDENTICAL_VERTICES_2D_PARAMS%"Yes"%TYPE_REPAIR%TYPE_REPAIR_PARAMS%"Yes"%SELF_INTERSECTING%SELF_INTERSECTING_PARAMS%"Yes"%PLANAR_SURFACE%PLANAR_SURFACE_PARAMS%"Yes"%SHELL_VALIDATION%""%"Yes"%SOLID_VOID_REPAIR%""%"Yes"%OGC_SIMPLE_CHECK%""%"No"%OGC_VALID_CHECK%""%"No"%MISSING_TEXTURE_COORDINATES%""%"Yes"%MISSING_VERTEX_NORMALS%""%"Yes"
    PASSED -> Tester
    FAILED -> VariableSetter
VariableSetter
    SCOPE = Global
    VALUE = yes
    VARNAME = _invalidFeatures
    -> AttributeCreator_2
AttributeCreator_2
    ATTR_LIST = error_label,Geometry
    -> DWGStyler
DWGStyler
    COLOR = 0.619608,0.0823529,1
    TEXT_ANNO_FORCE_VISIBLE = No
    DWGStyled -> Cloner
Tester
    BOOL_OP = OR
    TEST_CLAUSE = TEST @Value(DIAMETER) NOT_= 0
    TEST_MODE = Automatic
    FAILED -> VariableSetter_2
VariableSetter_2
    SCOPE = Global
    VALUE = yes
    VARNAME = _invalidFeatures
    -> AttributeCreator_3
AttributeCreator_3
    ATTR_LIST = error_label,Attribute: DIAMETER
    -> DWGStyler_2
DWGStyler_2
    COLOR = 0.596078,1,0.698039
    TEXT_ANNO_FORCE_VISIBLE = No
    DWGStyled -> Cloner
Cloner
    COPIES = 1
    COPYATT = _copynum
    COPY -> XMLTemplater_2 [ROOT]
    COPY -> Sampler
    COPY -> VariableRetriever_4
XMLTemplater_2
    OUTPUT_XML_HEADER = No
    RESULT_ATTRIBUTE = Remarks
    ROOT_QUERY_EXPR:
      <div style="min-width: 200px;">Invalid {fme:get-attribute("error_label")}
      </div>
    VISIBLE_QUERY_VALIDATE = No
    -> AttributeCreator

Bookmark: Report creation
AttributeCreator
    ATTR_LIST = _invalid_features,yes
    -> GoogleStaticMapCreator
GoogleStaticMapCreator
    -> StringReplacer
StringReplacer
    CASE = NO
    FIND_TEXT = http://
    NO_MATCH = _FME_NO_OP_
    REGEXP = NO
    REPLACE_TEXT = https://
    SRC_ATTRS = _StaticMapUrl
    -> Counter
Counter
    CNT_ATTR = _numFails
    DOMAIN = failcount
    SCOPE = Global
    START = 1
    -> Sampler_3
Sampler_3
    RATE = 1
    SAMPLE_MODE = No
    SAMPLE_TYPE_LONG = Last N Features
    SAMPLED -> VariableSetter_5
    NOT_SAMPLED -> XMLTemplater_3 [ROW]
VariableSetter_5
    SCOPE = Global
    VALUE = @Value(_numFails)
    VARNAME = totalFails
    -> XMLTemplater_3 [ROW]
Creator
    GEOMTYPE = Geometry Object
    NUM = 1
    CREATED -> VariableRetriever_2
VariableRetriever_2
    SCOPE = Global
    VALUE_ATTR = _invalidFeatures
    VARNAME = _invalidFeatures
    -> VariableRetriever
VariableRetriever
    SCOPE = Global
    VALUE_ATTR = _uuid
    VARNAME = uuid
    -> Tester_3
Tester_3
    BOOL_OP = OR
    TEST_CLAUSE = TEST @Value(_invalidFeatures) = yes
    TEST_MODE = Automatic
    PASSED -> XMLTemplater_3 [ROOT]
XMLTemplater_3
    OUTPUT_XML_HEADER = No
    RESULT_ATTRIBUTE = _htmlTable
    ROOT_QUERY_EXPR:
      <table>
      <tr>
      <th>TILE</th>
      <th>FEATURE_ID</th>
      <th>DIAMETER</th>
      <th>WNM_TYPE</th>
      <th>Error Remarks</th>
      <th>Map</th>
      </tr>
      {fme:process-features("ROW")}
      </table>
    ROW_QUERY_EXPR:
      <tr>
      <td>{fme:get-attribute("TILE")}</td>
      <td>{fme:get-attribute("FEATURE_ID")}</td>
      <td>{fme:get-attribute("DIAMETER")}</td>
      <td>{fme:get-attribute("WNM_TYPE")}</td>
      <td>{fme:get-xml-attribute("Remarks")}</td>
      <td><img src='{fme:get-attribute("_StaticMapUrl")}'></img></td>
      </tr>
    VISIBLE_QUERY_VALIDATE = No
    -> FeatureHolder_2
FeatureHolder_2
    -> VariableRetriever_5
VariableRetriever_5
    SCOPE = Global
    VALUE_ATTR = _totalCount
    VARNAME = totalChecked
    -> VariableRetriever_6
VariableRetriever_6
    SCOPE = Global
    VALUE_ATTR = _numFails
    VARNAME = totalFails
    -> StringConcatenator_3
    -> VariableRetriever_6_Output
VariableRetriever_6_Output: Logger
    LOG_FEATURE = LOG_ONLY
    MAXCOORDS = 20
    MAXFEATS = 20
    MESSAGE = Feature is:
    SEVERITY = INFO
StringConcatenator_3
    ACTION = Create New Attribute
    PARM_LINE:
      <!DOCTYPE html>
      <html>
      <head>
        <meta charset="utf-8">

        <!-- Use the .htaccess and remove these lines to avoid edge case issues. More info: h5bp.com/i/378 -->
        <meta http-equiv="X-UA-Compatible" content="IE=edge,chrome=1">

        <title>Data validation failure</title>
        <meta name="description" content="">

        <!-- Mobile viewport optimized: h5bp.com/viewport -->
        <meta name="viewport" content="width=device-width">

        <!-- CSS goes in the document HEAD or added to your external stylesheet -->
          <style type="text/css">
          /* ------------------
           styling for the tables
             ------------------   */
      #test {
              font-family: 'Lucida Sans Unicode', 'Lucida Grande', Sans-Serif;
              color: white;
              background-color: #505050;
          }
          table {
            line-height: 1.6em;
            font-size: 12px;
            background: #fff;
            background-color: #505050;
            border-collapse: collapse;
            text-align: center;
          }

          th {
            font-size: 14px;
            font-weight: bold;
            color: white;
            padding: 10px 8px;
            border-bottom: 2px solid white;
          }

          tr {
            color: white;
            padding: 9px 8px 0px 8px;
          }

          a {
            color: #f57f17;
          }

              a:hover {
            color: #f57f17;
          }

          </style>

      </head>
      <body>
      <div id="test">
      <h4>Results</h4>
      <p>@Value(_numFails) of @Value(_totalCount) features failed validation</p>
      <p><a href="$(FME_SERVER_WEB_URL)/fmerest/v3/resources/connections/FME_SHAREDRESOURCE_TEMP/filesys/CADError/errors_@Value(_uuid).dwg?fmetoken=18027380622e32bea2a7e4bc064685996bc6142e" target="_blank">Download failed features</a></p>

      @Value(_htmlTable)

      </div>
      </body>
      </html>
    VAL_ATTR = text_line_data
    -> text_line (writer TEXTLINE_1)

Bookmark: HTML report for success
Aggregator
    ACCUM_ATTRS_NAME = No
    COUNT_ATTR = _count
    MODE = Attributes Only
    ORDERED = No
    SEP = ,
    AGGREGATE -> TimeStamper
Note: Timestamp according to locale
TimeStamper
    FMT = ^c
    TIME_ATTR = _timestamp
    -> StringConcatenator_2
StringConcatenator_2
    ACTION = Create New Attribute
    PARM_LINE:
      fme_basicstring:791%18%35%14%31:<!doctype html>
      <head>
        <meta charset="utf-8">

        <!-- Use the .htaccess and remove these lines to avoid edge case issues. More info: h5bp.com/i/378 -->
        <meta http-equiv="X-UA-Compatible" content="IE=edge,chrome=1">

        <title></title>
        <meta name="description" content="">

        <!-- Mobile viewport optimized: h5bp.com/viewport -->
        <meta name="viewport" content="width=device-width">

         <style type="text/css">
          /* ------------------
           styling for the tables
             ------------------   */

         #test{
              font-family: 'Lucida Sans Unicode', 'Lucida Grande', Sans-Serif;
              color: white;
              background-color: #505050;
          }
          </style>

      </head>
      <body>
      <div id="test">
      <h4>Results</h4>
          <p>Load Complete - Data Validation was Successful</p>
          <p>Date Loaded:  @Value(_timestamp)<br>
          Number of Features Added: @Value(_count)</p>
          </div>
      </body>
      </html>
    VAL_ATTR = text_line_data
    -> text_line (writer TEXTLINE_1)

FME custom transformer GoogleStaticMapCreator

Input (input)
    -> Reprojector
Reprojector
    DEST = EPSG:4326
    INTERPOLATION_TYPE_NAME = Nearest Neighbor
    RASTER_CELL_SIZE = Preserve Cells
    SOURCE = TX83-CF
    STROKE_ARCS = Yes
    REPROJECTED -> CoordinateSwapper
CoordinateSwapper
    SWAP_TYPE = X <-> Y
    -> GeometryExtractor
GeometryExtractor
    ATTR = _geometry
    KIND_LONG = OGC Well Known Text
    OGCVERSION = 1.1
    -> SubstringExtractor
SubstringExtractor
    END = -2
    RESULT_ATTR = _path
    SRC_ATTR = _geometry
    START = 12
    -> StringReplacer_2
StringReplacer_2
    CASE = no
    FIND_TEXT = ,
    NO_MATCH = _FME_NO_OP_
    REGEXP = no
    REPLACE_TEXT = |
    SRC_ATTRS = _path
    -> StringReplacer
StringReplacer
    CASE = no
    FIND_TEXT = " "
    NO_MATCH = _FME_NO_OP_
    REGEXP = no
    REPLACE_TEXT = ,
    SRC_ATTRS = _path
    -> CoordinateExtractor
CoordinateExtractor
    IND = 0
    X_ATTR = _x
    Y_ATTR = _y
    Z_ATTR = _z
    Z_DEFAULT = -9999
    -> StringConcatenator_5
StringConcatenator_5
    PARM_LINE = http://maps.googleapis.com/maps/api/staticmap?center=@Value(_x),@Value(_y)&amp&amp&size=200x200&amp&sensor=false&path=color:0x0000ff|weight:5|@Value(_path)&key=AIzaSyAAJ9HjDtsSOYUzLI6Xkvfc8RMHOi6RfIs
    VAL_ATTR = _StaticMapUrl
    -> Output (output)
Output (output)
